Dim oSSet As SelectSet = ThisDoc.Document.SelectSet
If oSSet.count = 0 Then
	MessageBox.Show("You must select a drawing view first", "iLogic")
Exit Sub
End If

'Reference to the drawing view from the 1st selected object
Dim oView As DrawingView = trycast(oSSet.item(1), DrawingView)
iProperties.Value("Summary", "Comments") = oView.Label.FormattedText

arrSplitStrings1 = Split(oView.Label.FormattedText, " ")
Dim spltdString, SearchedChar, newStringJoin

	For Each spltdString In arrSplitStrings1
		Dim SearchChar As String = "FormatID" 
		strPos = InStr(spltdString, SearchChar)
		If strPos = 1 Then
			strV1 = spltdString
		End If
	Next
	newStringJoin = ""
	For Each SearchedChar In strV1
		If SearchedChar <> ">" Then
			newStringJoin += SearchedChar
		Else
			Exit For
		End If
	Next
	
MessageBox.Show(strV1, "Title")
MessageBox.Show(newStringJoin, "Title")

If oView IsNot Nothing Then
oView.ShowLabel = True
'format the model iproperties	
oPartNumber = "<StyleOverride Bold='True'>Pieza </StyleOverride><StyleOverride Bold='True'><Property Document='model' PropertySet='User Defined Properties' Property='ItemNumber' FormatID='{32853F0F-3444-11D1-9E93-0060B03C1CA6}'>ItemNumber</Property></StyleOverride><Br/>Cantidad: <Property Document='model' PropertySet='User Defined Properties' Property='ItemQuantity' FormatID='{D5CDD505-2E9C-101B-9397-08002B2CF9AE}'>ItemQuantity</Property><Br/><StyleOverride FontSize='0.3' Bold='True'>(</StyleOverride><StyleOverride FontSize='0.3' Bold='True'><DrawingViewScale/></StyleOverride><StyleOverride FontSize='0.3' Bold='True'>)</StyleOverride>"
'add To the view label
oView.Label.FormattedText = oPartNumber
Dim text1 As String = "<StyleOverride Bold='True'>Pieza </StyleOverride><StyleOverride Bold='True'><Property Document='model' PropertySet='User Defined Properties' Property='ItemNumber' " + strV1 + ">ItemNumber</Property></StyleOverride><Br/>Cantidad: <Property Document='model' PropertySet='User Defined Properties' Property='ItemQuantity' " + strV1 + "'>ItemQuantity</Property><Br/><StyleOverride FontSize='0.3' Bold='True'>(</StyleOverride><StyleOverride FontSize='0.3' Bold='True'><DrawingViewScale/></StyleOverride><StyleOverride FontSize='0.3' Bold='True'>)</StyleOverride>"

If text1=oPartNumber Then
	MessageBox.Show("OK", "Title")
End If

'MessageBox.Show(text1, "Title")
'MessageBox.Show(oPartNumber, "Title")


Else
	MessageBox.Show("The selected object is not a drawing view", "iLogic")
End If
