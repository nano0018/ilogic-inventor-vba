Dim oSSet As SelectSet = ThisDoc.Document.SelectSet
If oSSet.count = 0 Then
	MessageBox.Show("You must select a drawing view first", "iLogic")
Exit Sub
End If

'Reference to the drawing view from the 1st selected object
Dim oView As DrawingView = trycast(oSSet.item(1), DrawingView)

If oView IsNot Nothing Then
oView.ShowLabel = True
'format the model iproperties	
oPartNumber = "<StyleOverride Underline='False'> <Property Document='model' PropertySet='Design Tracking Properties' Property='Part Number' FormatID='{32853F0F-3444-11D1-9E93-0060B03C1CA6}' PropertyID='4'>PART NUMBER</Property></StyleOverride>"
oStringScale = "<Br/><StyleOverride FontSize='0.3'>( <DrawingViewScale/>)</StyleOverride>"

'add to the view label
oView.Label.FormattedText =  oPartNumber & oStringScale	    

Else
	MessageBox.Show("The selected object is not a drawing view", "iLogic")
End If
