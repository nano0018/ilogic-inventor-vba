'Dim oDoc As AssemblyDocument
Dim oDoc As PartDocument = ThisDoc.Document 'of : oDoc as AssemblyDocumment = ThisDoc.Document

Try
prop = oDoc.ComponentDefinition.Parameters.UserParameters.item ("SL")
Catch
newprop = oDoc.ComponentDefinition.Parameters.UserParameters.AddByExpression("SL", "0", "mm")
End Try

param =Parameter.Param("SL") 
param.ExposedAsProperty = True 
param.CustomPropertyFormat.ShowTrailingZeros = False 
param.CustomPropertyFormat.ShowLeadingZeros = False 
param.CustomPropertyFormat.ShowUnitsString = False 
param.CustomPropertyFormat.Units = "mm"

Try
prop = oDoc.ComponentDefinition.Parameters.UserParameters.item ("SW")
Catch
newprop = oDoc.ComponentDefinition.Parameters.UserParameters.AddByExpression("SW", "0", "mm")
End Try

param1 =Parameter.Param("SW") 
param1.ExposedAsProperty = True 
param1.CustomPropertyFormat.ShowTrailingZeros = False 
param1.CustomPropertyFormat.ShowLeadingZeros = False 
param1.CustomPropertyFormat.ShowUnitsString = False
param.CustomPropertyFormat.Units = "mm"

Parameter("SL")=SheetMetal.FlatExtentsLength
Parameter("SW")=SheetMetal.FlatExtentsWidth

param =Parameter.Param("Thickness") 
param.ExposedAsProperty = True 
param.CustomPropertyFormat.ShowTrailingZeros = False 
param.CustomPropertyFormat.ShowLeadingZeros = False 
param.CustomPropertyFormat.ShowUnitsString = False 
param.CustomPropertyFormat.Units = "mm"

param =Parameter.Param("ANCHO_PELDAÑO") 
param.ExposedAsProperty = True 
param.CustomPropertyFormat.ShowTrailingZeros = False 
param.CustomPropertyFormat.ShowLeadingZeros = False 
param.CustomPropertyFormat.ShowUnitsString = False
param.CustomPropertyFormat.Units = "mm"

param =Parameter.Param("LARGO_PELDAÑO") 
param.ExposedAsProperty = True 
param.CustomPropertyFormat.ShowTrailingZeros = False 
param.CustomPropertyFormat.ShowLeadingZeros = False 
param.CustomPropertyFormat.ShowUnitsString = False 
param.CustomPropertyFormat.Units = "mm"

param =Parameter.Param("ALTO_PELDAÑO") 
param.ExposedAsProperty = True 
param.CustomPropertyFormat.ShowTrailingZeros = False 
param.CustomPropertyFormat.ShowLeadingZeros = False 
param.CustomPropertyFormat.ShowUnitsString = False 
param.CustomPropertyFormat.Units = "mm"

iProperties.Value("Project", "Description")="=Lámina Alfajor Aluminio <SL> x <SW>"
iProperties.Value("Project", "Part Number")="=Peldaño <ANCHO_PELDAÑO> x <LARGO_PELDAÑO> x <ALTO_PELDAÑO>"

Dim oPartDoc As PartDocument
 oPartDoc=ThisApplication.ActiveDocument
 Dim oParameter As Parameter
 Dim oFormat As CustomPropertyFormat 
 For Each oParameter In oPartDoc.ComponentDefinition.Parameters.UserParameters 
 oFormat=oParameter.CustomPropertyFormat 
 oParameter.ExposedAsProperty=True

 oFormat.PropertyType=Inventor.CustomPropertyTypeEnum.kTextPropertyType
 oFormat.Precision=Inventor.CustomPropertyPrecisionEnum.kZeroDecimalPlacePrecision
 oFormat.Units="mm"
 oFormat.ShowUnitsString=True
 oFormat.ShowLeadingZeros=True
 oFormat.ShowTrailingZeros=False
Next oParameter
