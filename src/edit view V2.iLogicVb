Dim oSSet As SelectSet = ThisDoc.Document.SelectSet
If oSSet.count = 0 Then
	MessageBox.Show("You must select a drawing view first", "iLogic")
Exit Sub
End If

'Reference to the drawing view from the 1st selected object
Dim oView As DrawingView = trycast(oSSet.item(1), DrawingView)

If oView IsNot Nothing Then
oView.ShowLabel = True
'format the model iproperties	
oComments = "<StyleOverride Underline='False'> <Property Document='model' PropertySet='Design Tracking Properties' Property='Cost Center' FormatID='{32853F0F-3444-11D1-9E93-0060B03C1CA6}' PropertyID='5'>COST CENTER</Property></StyleOverride>"
oStringScale = "<Br/><StyleOverride FontSize='0.3'>( <DrawingViewScale/>)</StyleOverride>"

'add to the view label
oView.Label.FormattedText =  "Parte#" & oComments & oStringScale	    

Else
	MessageBox.Show("The selected object is not a drawing view", "iLogic")
End If
