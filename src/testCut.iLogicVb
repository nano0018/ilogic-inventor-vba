Dim oSSet As SelectSet = ThisDoc.Document.SelectSet
If oSSet.count = 0 Then
	MessageBox.Show("You must select a drawing view first", "iLogic")
Exit Sub
End If

'Reference to the drawing view from the 1st selected object
Dim oView As DrawingView = trycast(oSSet.item(1), DrawingView)

If oView IsNot Nothing Then
oView.ShowLabel = True
'format the model iproperties	
oPartNumber = "<DrawingViewName/>-<DrawingViewName/> ( <DrawingViewScale/> )<Br/>"

'add to the view label
oView.Label.FormattedText =  oPartNumber

Else
	MessageBox.Show("The selected object is not a drawing view", "iLogic")
End If
